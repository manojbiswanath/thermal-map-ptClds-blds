FME workspace pointcloud_transform.fmw

Parameters:
- SourceDataset_LAS_5 = $(FME_MF_DIR)filtered_simplified\New folder\SubTCA_simplified2_transformed_FME_affiner.las   # Source ASPRS LAS File(s)
- SourceDataset_LAS_3 = $(FME_MF_DIR)filtered_simplified\New folder\SubTCA_simplified2.las   # Source ASPRS LAS File(s)
- SourceDataset_PCD = $(FME_MF_DIR)filtered_simplified\New folder\SubTCA_simplified2.pcd   # Point Cloud Data File(s)

Readers:
- LAS_1: LAS from $(SourceDataset_LAS_5)
- LAS_2: LAS from $(SourceDataset_LAS_3)
- PCD_1: PCD from $(SourceDataset_PCD)

CsmapReprojector
    DEST = EPSG:25832
    INTERPOLATION_TYPE_NAME = Nearest Neighbor
    RASTER_CELL_SIZE = Preserve Cells
    RASTER_TOLERANCE = 0.0
    SOURCE = WGS84.Geocentric_FME
    VERTICAL_HANDLING = Heights are relative to the ellipsoid(s) or geocentric
    REPROJECTED -> 3DRotator
3DRotator
    ANGLE = 1.7
    AXIS_CHOICE = Z Axis
    ROTATED -> Offsetter
Offsetter
    MODE = Cartesian Coordinate
    XOFF = 0
    YOFF = 0
    ZOFF = -48
    OFFSET -> LAS
LAS: Inspector
PCD (reader PCD_1)
    -> 3DAffiner
3DAffiner
    A = -0.20053982643488838
    B = -0.72975436304732511
    C = 0.653637780140389870
    D = 4177139.442822214700
    E = 0.979685550579095120
    F = -0.14937937302342402
    G = 0.133798448801411370
    H = 855052.7445900742900
    I = 0.000000000000000000
    J = 0.667191406216027790
    K = 0.744886318488585660
    L = 4728408.463954962800
    AFFINED -> PCD
PCD: Inspector
LAS (reader LAS_2)
    -> Offsetter_2
Offsetter_2
    MODE = Cartesian Coordinate
    XOFF = 691041.3864013541
    YOFF = 5336089.741879154
    ZOFF = 540.2139999999999
    OFFSET -> LAS_2
LAS_2: Inspector

Bookmark: Reader Feature Types
LAS (reader LAS_1)
    -> CsmapReprojector
